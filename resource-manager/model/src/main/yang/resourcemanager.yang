module resourcemanager {
    yang-version 1;
    namespace "urn:eu:virtuwind:resourcemanager";
    prefix resourcemanager;

    description "Resource Manger configuration";

    revision "2016-10-17" {
        description "Initial version of resourcemanager interfaces";
    }

    rpc create-and-send-flow {
        input {
            leaf sourceIP {
                type string;
            }
            leaf destinationIP {
                type string;
            }
            leaf source-port {
                type int32;
            }
            leaf dest-port {
                 type int32;
            }
            leaf protocol {
                type int32;
            }
            list physical-path-links {
                leaf link {
                    type string;
                }
            }
            list queues-on-path {
                leaf queue {
                    type int32;
                }
            }
            list meters {
                leaf meter {
                    type int32;
                }
            }
            leaf src-node {
                type string;
            }
            leaf dest-node {
                type string;
            }
            leaf src-node-port {
                type string;
            }
            leaf dest-node-port {
                type string;
            }

        }
        output{
        	leaf response {
                type string;
            }
        } 
    }


    rpc best-embeded-flow {
         input {
                    leaf sourceIP {
                        type string;
                    }
                    leaf destinationIP {
                        type string;
                    }
                    leaf source-port {
                        type int32;
                    }
                    leaf dest-port {
                         type int32;
                    }
                    leaf protocol {
                        type int32;
                    }
                    list physical-path-links {
                        leaf link {
                            type string;
                        }
                    }
                    leaf idletimeout {
                        type int32;
                    }
                    leaf hardtimeout {
                        type int32;
                    }
                    list meters {
                        leaf meter {
                            type int32;
                        }
                    }
                    leaf src-node {
                        type string;
                    }
                    leaf dest-node {
                        type string;
                    }
                    leaf src-node-port {
                        type string;
                    }
                    leaf dest-node-port {
                        type string;
                    }

                }
        output{
        	leaf response {
                type string;
            }
        }
    }


    rpc configure-fast-failover-groups {
    	input{
    		list path {
                leaf link {
                    type string;
                }
            }
            leaf ffport {
                type int32;
            }
    	}
        output{
        	leaf response {
                type string;
            }
        }
        
    }

    rpc embedMplsPath {
    	input{
    		leaf mplsLabel {
                type int32;
            }
            list links {
                leaf link {
                    type string;
                }
            }
            leaf queue-id {
                type int32;
            }	
    	}
        output{
        	leaf response {
                type string;
            }
        }
        
    }

    rpc embedMplsFlow {
    	input{
    		leaf mpls-label {
                type int32;
            }
            leaf dst-mac {
                type string;
            }
            leaf mac-to-modify {
                type string;
            }
            leaf queue-id {
                type int32;
            }	
    	}

        output{
        	leaf response {
                type string;
            }
        }
        
    }




}
